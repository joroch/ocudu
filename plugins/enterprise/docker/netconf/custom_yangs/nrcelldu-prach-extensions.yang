//
// Copyright 2021-2025 Software Radio Systems Limited
//
// By using this file, you agree to the terms and conditions set
// forth in the LICENSE file which can be found at the top level of
// the distribution.
//

module nrcelldu-prach-extensions {
    yang-version 1.1;
    namespace "urn:ocudu-nrcelldu-prach-extension:1.0";
    prefix "ocudu-nrcelldu-prach";
    
    organization "Software Radio Systems Ltd";
    description "The module defines YANG extensions needed for OCUDU
                 Copyright (c) 2024-2025 Software Radio Systems. All rights reserved.";
    revision 2025-01-08 { description "Initial version"; }

    grouping prach_extensions_subtree {
        description "OCUDU Extension of 3gpp PRACH config";

        container srs_nrcelldu_prach_extensions {
            leaf prach_config_index {
                type int32 { range 0..255; }
                description "PRACH configuration index. If not set, the value is derived, so that the PRACH fits in an UL slot.";
            }

            leaf prach_root_sequence_index {
                description "PRACH root sequence index, see TS 38.211, clause 6.3.3.1.";
                type prach_root_seq_index_value;
                default "1";
            }
        }        
    }

    typedef prach_root_seq_index_value {
        type int32 { range 1..839; }
    }
}
