//
// Copyright 2021-2025 Software Radio Systems Limited
//
// By using this file, you agree to the terms and conditions set
// forth in the LICENSE file which can be found at the top level of
// the distribution.
//

module nrcelldu-extensions {
    yang-version 1.1;
    namespace "urn:ocudu-nrcelldu-extension:1.0";
    prefix "ocudu-nrcelldu";

    import _3gpp-common-managed-element { prefix me3gpp; }
    import _3gpp-nr-nrm-gnbdufunction { prefix gnbdu3gpp; }
    import _3gpp-nr-nrm-nrcelldu { prefix nrcelldu3gpp; }
    
    import nrcelldu-ssb-extensions { prefix ocudu-nrcelldu-ssb; }
    import nrcelldu-prach-extensions { prefix ocudu-nrcelldu-prach; }
    import nrcelldu-ofh-extensions { prefix ocudu-nrcelldu-ofh; }
    import nrcelldu-pdsch-extensions { prefix ocudu-nrcelldu-pdsch; }
    import nrcelldu-base-extensions { prefix ocudu-nrcelldu-base; }
    import nrcelldu-tdd-extensions { prefix ocudu-nrcelldu-tdd; }
    
    organization "Software Radio Systems Ltd";
    description "The module defines YANG extensions needed for OCUDU
                 Copyright (c) 2024-2025 Software Radio Systems. All rights reserved.";
    revision 2025-01-08 { description "Initial version"; }

    grouping nrcelldu_extensions_subtree {

        container srs_nrcelldu_extensions {
            description "OCUDU extension of 3gpp NRCellDU config";

            uses ocudu-nrcelldu-base:base_extensions_subtree;
            uses ocudu-nrcelldu-ofh:ofh_extensions_subtree;
            uses ocudu-nrcelldu-ssb:ssb_extensions_subtree;
            uses ocudu-nrcelldu-prach:prach_extensions_subtree;
            uses ocudu-nrcelldu-pdsch:pdsch_extensions_subtree;
            uses ocudu-nrcelldu-tdd:tdd_extensions_subtree;
        }          
    }

    augment /me3gpp:ManagedElement/gnbdu3gpp:GNBDUFunction/nrcelldu3gpp:NRCellDU/nrcelldu3gpp:attributes {
        uses nrcelldu_extensions_subtree;
    }
}
