//
// Copyright 2021-2025 Software Radio Systems Limited
//
// By using this file, you agree to the terms and conditions set
// forth in the LICENSE file which can be found at the top level of
// the distribution.
//

module gnbdufunction-extensions {
    yang-version 1.1;
    namespace "urn:ocudu-gnbdufunction-extension:1.0";
    prefix "ocudu-gnbdufunction";

    import _3gpp-common-managed-element { prefix me3gpp; }
    import _3gpp-nr-nrm-gnbdufunction { prefix gnbdu3gpp; }
    
    import gnbdufunction-testmode-extensions { prefix ocudu-gnbdufunction-testmode; }
    import gnbdufunction-log-extensions { prefix ocudu-gnbdufunction-log; }
    import hal-extensions { prefix ocudu-hal; }
    import metrics-extensions { prefix ocudu-metrics; }
    import remote-control-extensions { prefix ocudu-remote-control; }
    
    organization "Software Radio Systems Ltd";
    description "The module defines YANG extensions needed for OCUDU
                 Copyright (c) 2024-2025 Software Radio Systems. All rights reserved.";
    revision 2025-01-08 { description "Initial version"; }

    grouping gnbdufunction_extensions_subtree {

        container srs_gnbdufunction_extensions {
            description "OCUDU extension of GNBDUFunction";

            uses ocudu-gnbdufunction-testmode:testmode_extensions_subtree;
            uses ocudu-gnbdufunction-log:log_extensions_subtree;
            uses ocudu-hal:hal_extensions_subtree;
            uses ocudu-metrics:metrics_extensions_subtree;
            uses ocudu-remote-control:remote_control_extensions_subtree;
        }          
    }

    augment /me3gpp:ManagedElement/gnbdu3gpp:GNBDUFunction {
        uses gnbdufunction_extensions_subtree;
    }
}
