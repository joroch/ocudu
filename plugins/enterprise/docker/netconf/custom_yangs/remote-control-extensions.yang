//
// Copyright 2021-2025 Software Radio Systems Limited
//
// By using this file, you agree to the terms and conditions set
// forth in the LICENSE file which can be found at the top level of
// the distribution.
//

module remote-control-extensions {
    yang-version 1.1;
    namespace "urn:ocudu-remote-control-extensions:1.0";
    prefix "ocudu-remote-control";

    import ietf-inet-types { prefix inet; }

    organization "Software Radio Systems Ltd";
    description "YANG extensions exposing remote control configuration defaults for OCUDU.";

    revision 2025-01-08 {
        description "Initial version.";
    }

    grouping remote_control_extensions_subtree {
        description "OCUDU extensions for remote control configuration.";

        container srs_remote_control_extensions {
            description "Remote control specific configuration options.";

            leaf enabled {
                description "Enable or disable the remote control service.";
                type boolean;
                default "true";
            }

            leaf bind_addr {
                description "IP address that the remote control service binds to.";
                type inet:ip-address;
                default "0.0.0.0";
            }
        }
    }
}
