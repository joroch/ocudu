//
// Copyright 2021-2025 Software Radio Systems Limited
//
// By using this file, you agree to the terms and conditions set
// forth in the LICENSE file which can be found at the top level of
// the distribution.
//

module nrcelldu-ssb-extensions {
    yang-version 1.1;
    namespace "urn:ocudu-nrcelldu-ssb-extension:1.0";
    prefix "ocudu-nrcelldu-ssb";
   
    organization "Software Radio Systems Ltd";
    description "The module defines YANG extensions needed for OCUDU
                 Copyright (c) 2024-2025 Software Radio Systems. All rights reserved.";
    revision 2025-01-08 { description "Initial version"; }

    grouping ssb_extensions_subtree {
        description "OCUDU Extension of 3gpp SSB config";

        container srs_nrcelldu_ssb_extensions {

            leaf ssb_period {
                description "Period of SSB scheduling in milliseconds";
                type int32;
                default "10";
            }

            leaf ssb_block_power_dbm {
                description "SS_PBCH_power_block in dBm";
                type ssb_block_power;
                default "-16";
            }
        }
    }

    typedef ssb_block_power {
        type int32 { range -60..50; }
        units dbm;
    }
}
